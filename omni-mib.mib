--  Title:    OMNI-MIB.MIB
--  Version:  v1.12
--  Date:     20 September 2021
--
--  Copyright (C) 2014-2021 Omnitronics Pty Ltd
--
--  This MIB defines objects for all Omnitronics Devices
--

OMNI-MIB DEFINITIONS ::= BEGIN

--
--  IMPORTS
--
--  SNMPv2-SMI : RFC2578 (Structure of Management Information Version 2)
--
--  SNMPv2-TC  : RFC2579 (Textual Conventions for SMIv2)
--
--  SNMPv2-CONF: RFC2580 (Conformance Statements for SMIv2)
--
IMPORTS
    OBJECT-TYPE,MODULE-IDENTITY , NOTIFICATION-TYPE,
    enterprises,
    Integer32,Counter32                FROM SNMPv2-SMI
    DisplayString                      FROM SNMPv2-TC
    OBJECT-GROUP,NOTIFICATION-GROUP    FROM SNMPv2-CONF;

--
--  For SNMPv2 the MODULE-IDENTITY must immediately follow the IMPORT construct.
--
--  27053 is the IANA-assigned number for Omnitronics.
--
omnitronics MODULE-IDENTITY
    LAST-UPDATED "202107020000Z"
    ORGANIZATION "Omnitronics"
    CONTACT-INFO
    "
      Omnitronics Pty Ltd
      27 Sarich Court
      Osborne Park
      Perth, Australia"

    DESCRIPTION
            "Omnitronics Enterprise MIBS: Omnitronics Radio interface Products"

    REVISION    "202107020000Z"
    DESCRIPTION
            "Omnitronics MIB file that describes OIDs used by all Omnitronics radio interface products"
    ::= { enterprises 27053 }

--
--  OIDs linked to omnitronics
--
omniNotifications   OBJECT IDENTIFIER ::=  { omnitronics   0 }
omniProducts        OBJECT IDENTIFIER ::=  { omnitronics   1 }
omniVersion         OBJECT IDENTIFIER ::=  { omnitronics   2 }
omniVoip            OBJECT IDENTIFIER ::=  { omnitronics   3 }
omniRadio           OBJECT IDENTIFIER ::=  { omnitronics   4 }
omniMessages        OBJECT IDENTIFIER ::=  { omnitronics   5 }
omniLinker          OBJECT IDENTIFIER ::=  { omnitronics   6 }
omniServer          OBJECT IDENTIFIER ::=  { omnitronics   7 }
omniMIBGroups       OBJECT IDENTIFIER ::=  { omnitronics   99 }

--
--  OIDs linked to omniProducts
--
ipr100              OBJECT IDENTIFIER ::=  { omniProducts  1 }
ipr120              OBJECT IDENTIFIER ::=  { omniProducts  2 }
ipr110              OBJECT IDENTIFIER ::=  { omniProducts  3 }
ipr400              OBJECT IDENTIFIER ::=  { omniProducts  4 }
ipe                 OBJECT IDENTIFIER ::=  { omniProducts  5 }
afi                 OBJECT IDENTIFIER ::=  { omniProducts  6 }
liu                 OBJECT IDENTIFIER ::=  { omniProducts  7 }
dsri                OBJECT IDENTIFIER ::=  { omniProducts  8 }
dx64                OBJECT IDENTIFIER ::=  { omniProducts  9 }
drg                 OBJECT IDENTIFIER ::=  { omniProducts  10 }
scu                 OBJECT IDENTIFIER ::=  { omniProducts  11 }
oem                 OBJECT IDENTIFIER ::=  { omniProducts  12 }
omnicoreWeb         OBJECT IDENTIFIER ::=  { omniProducts  20 }
omnicoreConsole     OBJECT IDENTIFIER ::=  { omniProducts  25 }
omnigate            OBJECT IDENTIFIER ::=  { omniProducts  30 }
tetragateway        OBJECT IDENTIFIER ::=  { omniProducts  31 }
omnihub             OBJECT IDENTIFIER ::=  { omniProducts  32 }

---
---   Textual Conventions
---
---
---  Notification Objects: omniNotifications
---
omniEventVoipLinkStatus  NOTIFICATION-TYPE
     OBJECTS {
        omniVoipLinkUp,
        omniVoipChannelName
     }
     STATUS current
     DESCRIPTION
         "VoIP link status change. 0  = Link down, 1 = link up, 255= disabled."
     ::= { omniNotifications 1 }

omniEventVoipRxSeqErrPackets NOTIFICATION-TYPE
     OBJECTS {
        omniVoipRxSequenceErrorPackets
    }
    STATUS current
     DESCRIPTION
         "VoIP Link has too many missing or incorrect sequence numbers"
     ::= { omniNotifications 2 }

omniEventVoipRxTooLatePackets NOTIFICATION-TYPE
     OBJECTS {
        omniVoipRxTooLatePackets
    }
    STATUS current
     DESCRIPTION
         "VoIP Link has too many packets that arrived too late to be played"
     ::= { omniNotifications 3 }

omniEventPushToTalkTimeout  NOTIFICATION-TYPE
     OBJECTS {
         omniRadioPushToTalk
     }
     STATUS current
     DESCRIPTION
         "Radio Push-To-Talk Timeout"
     ::= { omniNotifications 4  }

omniEventConfigChange NOTIFICATION-TYPE
    STATUS current
    DESCRIPTION
         "IPR Device Configuration has changed"
     ::= { omniNotifications 5 }

omniEventInformation NOTIFICATION-TYPE
    OBJECTS {
        omniInformationMessage
    }
    STATUS current
    DESCRIPTION
         "General information trap send by an Omnitronics device"
     ::= { omniNotifications 6 }

omniEventWarning NOTIFICATION-TYPE
    OBJECTS {
        omniWarningMessage
    }
    STATUS current
    DESCRIPTION
         "General warning trap send by an Omnitronics device"
     ::= { omniNotifications 7 }

omniEventError NOTIFICATION-TYPE
    OBJECTS {
        omniErrorMessage
    }
    STATUS current
    DESCRIPTION
         "General error trap send by an Omnitronics device"
     ::= { omniNotifications 8 }
spectraEvtAlarm  NOTIFICATION-TYPE
     OBJECTS {
        spectraLEDAlarm
     }
     STATUS current
     DESCRIPTION
         "Indicates a change in the Alarm LED status"
     ::= { omniNotifications 9 }

spectraEvtLockDetect  NOTIFICATION-TYPE
     OBJECTS {
        spectraLEDLockDetect
     }
     STATUS current
     DESCRIPTION
         "Indicates a change in the Lock detect LED status"
     ::= { omniNotifications 10 }

spectraEvtCTCSS  NOTIFICATION-TYPE
     OBJECTS {
        spectraLEDCTCSS
     }
     STATUS current
     DESCRIPTION
         "Indicates a change in the CTCSS or Low supply power LED status"
     ::= { omniNotifications 11 }

spectraEvtPTT  NOTIFICATION-TYPE
     OBJECTS {
        spectraLEDPTT
     }
     STATUS current
     DESCRIPTION
         "Indicates a change in the PTT LED status"
     ::= { omniNotifications 12 }

spectraEvtMute  NOTIFICATION-TYPE
     OBJECTS {
        spectraLEDMute
     }
     STATUS current
     DESCRIPTION
         "Indicates a change in the Mute LED status"
     ::= { omniNotifications 13 }

spectraEvtPower  NOTIFICATION-TYPE
     OBJECTS {
        spectraLEDPower
     }
     STATUS current
     DESCRIPTION
         "Indicates a change in the Power LED status"
     ::= { omniNotifications 14 }

spectraEvtLowForwardPower  NOTIFICATION-TYPE
     OBJECTS {
        spectraAlarmLowForwardPower
     }
     STATUS current
     DESCRIPTION
         "Indicates a change in the Low Forward Power alarm status"
     ::= { omniNotifications 15 }

spectraEvtHighReflectedPower  NOTIFICATION-TYPE
     OBJECTS {
        spectraAlarmHighReflectedPower
     }
     STATUS current
     DESCRIPTION
         "Indicates a change in the High Reflected Power alarm status"
     ::= { omniNotifications 16 }

spectraEvtLowInputVoltage  NOTIFICATION-TYPE
     OBJECTS {
        spectraAlarmLowInputVoltage
     }
     STATUS current
     DESCRIPTION
         "Indicates a change in the Low Input Voltage alarm status"
     ::= { omniNotifications 17 }

spectraEvtHighInputVoltage  NOTIFICATION-TYPE
     OBJECTS {
        spectraAlarmHighInputVoltage
     }
     STATUS current
     DESCRIPTION
         "Indicates a change in the High Input Voltage alarm status"
     ::= { omniNotifications 18 }

spectraEvtTransmitterOutOfLock  NOTIFICATION-TYPE
     OBJECTS {
        spectraAlarmTransmitterOutOfLock
     }
     STATUS current
     DESCRIPTION
         "Indicates a change in the Transmitter Out of Lock alarm status"
     ::= { omniNotifications 19 }

spectraEvtReceiverOutOfLock  NOTIFICATION-TYPE
     OBJECTS {
        spectraAlarmReceiverOutOfLock
     }
     STATUS current
     DESCRIPTION
         "Indicates a change in the Receiver Out of Lock alarm status"
     ::= { omniNotifications 20 }
spectraEvtPAOverTemperature  NOTIFICATION-TYPE
     OBJECTS {
        spectraAlarmPAOverTemperature
     }
     STATUS current
     DESCRIPTION
         "Indicates a change in the PA Over Temperature alarm status"
     ::= { omniNotifications 21 }

spectraEvtOpenCollectorPolarity  NOTIFICATION-TYPE
     OBJECTS {
        spectraOpenCollectorPolarity
     }
     STATUS current
     DESCRIPTION
         "Indicates a change in the Open Collector Polarity alarm status"
     ::= { omniNotifications 22 }

 
---
---  Message Information: omniMessages
---
omniInformationMessage OBJECT-TYPE
    SYNTAX DisplayString (SIZE (255))
    MAX-ACCESS read-only
    STATUS current
    DESCRIPTION
        "General information message send by an Omnitronics device"
    ::= { omniMessages 1 }

omniWarningMessage OBJECT-TYPE
    SYNTAX DisplayString (SIZE (255))
    MAX-ACCESS read-only
    STATUS current
    DESCRIPTION
        "General warning message send by an Omnitronics device"
    ::= { omniMessages 2 }

omniErrorMessage OBJECT-TYPE
    SYNTAX DisplayString (SIZE (255))
    MAX-ACCESS read-only
    STATUS current
    DESCRIPTION
        "General error message send by an Omnitronics device"
    ::= { omniMessages 3 }

---
---  Version Information: omniVersion information
---

applicationVersion OBJECT-TYPE
    SYNTAX DisplayString (SIZE (255))
    MAX-ACCESS read-only
    STATUS current
    DESCRIPTION
        "Version number for main application"
    ::= { omniVersion 1 }

dspVersion OBJECT-TYPE
    SYNTAX DisplayString (SIZE (255))
    MAX-ACCESS read-only
    STATUS current
    DESCRIPTION
        "Version number for DSP/API application"
    ::= { omniVersion 2 }

serialNumber OBJECT-TYPE
    SYNTAX DisplayString (SIZE (255))
    MAX-ACCESS read-only
    STATUS current
    DESCRIPTION
        "Device serial number"
    ::= { omniVersion 3 }

hardwareRevision OBJECT-TYPE
    SYNTAX DisplayString (SIZE (255))
    MAX-ACCESS read-only
    STATUS current
    DESCRIPTION
        "Device hardware revision"
    ::= { omniVersion 4 }

---
---  Voip Information: omniVoip
---
omniVoipNumberOfChannels OBJECT-TYPE
    SYNTAX Integer32(0..128)
    MAX-ACCESS read-only
    STATUS current
    DESCRIPTION "Number of Voip Channels supported by this device"
        ::= { omniVoip 1 }

omniVoipStatusTable OBJECT-TYPE
    SYNTAX      SEQUENCE OF OmniVoipStatusEntry
    MAX-ACCESS  not-accessible
    STATUS      current
    DESCRIPTION
        "Table contains the status of VoIP links"
    ::=  { omniVoip 2 }

omniVoipStatusEntry OBJECT-TYPE
        SYNTAX      OmniVoipStatusEntry
        MAX-ACCESS  not-accessible
        STATUS      current
        DESCRIPTION
            "Row describes status of a Voip connection"
        INDEX   { omniVoipChannelIndex }
        ::= { omniVoipStatusTable 1 }

OmniVoipStatusEntry ::=
    SEQUENCE {
        omniVoipChannelIndex           Integer32,
        omniVoipChannelName            DisplayString,
        omniVoipLinkUp                 Integer32,
        omniVoipABCDState              Integer32,
        omniVoipTransmitPackets        Counter32,
        omniVoipRxPackets              Counter32,
        omniVoipRxSequenceErrorPackets Counter32,
        omniVoipRxTooLatePackets       Counter32,
        omniRadioChannelNumber         Integer32
    }

omniVoipChannelIndex OBJECT-TYPE
    SYNTAX      Integer32(0..3)
    MAX-ACCESS  not-accessible
    STATUS      current
    DESCRIPTION
        "Index for OmniVoip table"
    ::= { omniVoipStatusEntry 1 }

omniVoipChannelName OBJECT-TYPE
    SYNTAX      DisplayString
    MAX-ACCESS  read-only
    STATUS      current
    DESCRIPTION
    "Name / SDES Location of channel "
    ::= { omniVoipStatusEntry 2 }

omniVoipLinkUp OBJECT-TYPE
    SYNTAX      Integer32(0..255)
    MAX-ACCESS  read-only
    STATUS      current
    DESCRIPTION
    "Current status of the VoIP link. 0=Offline, 1=online, 255=Disabled "
    ::= { omniVoipStatusEntry 3 }

omniVoipABCDState OBJECT-TYPE
    SYNTAX      Integer32(0..16)
    MAX-ACCESS  read-only
    STATUS      current
    DESCRIPTION
    "Current received Telephone ABCD bits (includes remote busy state)"
    ::= { omniVoipStatusEntry 4 }

omniVoipTransmitPackets OBJECT-TYPE
    SYNTAX      Counter32
    MAX-ACCESS  read-only
    STATUS      current
    DESCRIPTION
        "Number of transmitted RTP packets since start-up"
    ::= { omniVoipStatusEntry 5 }

omniVoipRxPackets OBJECT-TYPE
    SYNTAX      Counter32
    MAX-ACCESS  read-only
    STATUS      current
    DESCRIPTION
        "Number of received RTP packets since start-up"
    ::= { omniVoipStatusEntry 6 }

omniVoipRxSequenceErrorPackets OBJECT-TYPE
    SYNTAX      Counter32
    MAX-ACCESS  read-only
    STATUS      current
    DESCRIPTION
        "Number of received RTP packets since start-up with incorrect sequence number, includes packets that have been lost"
    ::= { omniVoipStatusEntry 7 }

omniVoipRxTooLatePackets OBJECT-TYPE
    SYNTAX      Counter32
    MAX-ACCESS  read-only
    STATUS      current
    DESCRIPTION
        "Number of received RTP packets since startup that have been received too late to be played"
    ::= { omniVoipStatusEntry 8 }

omniRadioChannelNumber OBJECT-TYPE
    SYNTAX      Integer32(1..899)
    MAX-ACCESS  read-write
    STATUS      current
    DESCRIPTION
    "Shows the current radio channel and can be used to trigger a channel change request."
    ::= { omniVoipStatusEntry 9 }

---
---  Radio Information: omniRadio
---
omniRadioNumberOfChannels OBJECT-TYPE
    SYNTAX Integer32(0..128)
    MAX-ACCESS read-only
    STATUS current
    DESCRIPTION
        "Number of Radio Channels supported by this device"
        ::= { omniRadio 1 }

omniRadioStatusTable OBJECT-TYPE
    SYNTAX      SEQUENCE OF OmniRadioStatusEntry
    MAX-ACCESS  not-accessible
    STATUS      current
    DESCRIPTION
        "This table contains the status of the Radio links for this
        including Omnitronics specifics"
    ::=  { omniRadio 2 }

omniRadioStatusEntry OBJECT-TYPE
    SYNTAX      OmniRadioStatusEntry
    MAX-ACCESS  not-accessible
    STATUS      current
    DESCRIPTION
        "Row describing the status of a Radio connection"
    INDEX   { omniRadioChannelIndex }
    ::= { omniRadioStatusTable 1 }

OmniRadioStatusEntry ::= SEQUENCE {
    omniRadioChannelIndex            Integer32,
    omniRadioChannelName             DisplayString,
    omniRadioBusy                    Integer32,
    omniRadioPushToTalk              Integer32,
    spectraLEDAlarm                  Integer32,
    spectraLEDLockDetect             Integer32,
    spectraLEDCTCSS                  Integer32,
    spectraLEDPTT                    Integer32,
    spectraLEDMute                   Integer32,
    spectraLEDPower                  Integer32,
    spectraAlarmLowForwardPower      Integer32,
    spectraAlarmHighReflectedPower   Integer32,
    spectraAlarmLowInputVoltage      Integer32,
    spectraAlarmHighInputVoltage     Integer32,
    spectraAlarmTransmitterOutOfLock Integer32,
    spectraAlarmReceiverOutOfLock    Integer32,
    spectraAlarmPAOverTemperature    Integer32,
    spectraOpenCollectorPolarity     Integer32
}

omniRadioChannelIndex OBJECT-TYPE
    SYNTAX      Integer32(0..3)
    MAX-ACCESS  not-accessible
    STATUS      current
    DESCRIPTION
        "Index for OmniRadio table"
    ::= { omniRadioStatusEntry 1 }

omniRadioChannelName OBJECT-TYPE
    SYNTAX      DisplayString
    MAX-ACCESS  read-only
    STATUS      current
    DESCRIPTION
        "Name of radio channel"
    ::= { omniRadioStatusEntry 2 }

omniRadioBusy OBJECT-TYPE
    SYNTAX      Integer32(0..1)
    MAX-ACCESS  read-only
    STATUS      current
    DESCRIPTION
    "Current radio busy (input) state. 0 is Off, 1 is On"
    ::= { omniRadioStatusEntry 3 }

omniRadioPushToTalk OBJECT-TYPE
    SYNTAX      Integer32(0..1)
    MAX-ACCESS  read-only
    STATUS      current
    DESCRIPTION
    "Current radio push to talk (output) state. 0 is Off, 1 is On"
    ::= { omniRadioStatusEntry 4 }

---
---  Linker Information: omniLinker
---
omniLinkerVoipTable OBJECT-TYPE
    SYNTAX      SEQUENCE OF OmniLinkerVoipEntry
    MAX-ACCESS  not-accessible
    STATUS      current
    DESCRIPTION
        "This table shows the current linker configuration between VOIP and radio channels.
        It also allows the audio, of radios linked to a VOIP channel, to be bridged."
    ::=  { omniLinker 1 }

omniLinkerVoipEntry OBJECT-TYPE
    SYNTAX      OmniLinkerVoipEntry
    MAX-ACCESS  not-accessible
    STATUS      current
    DESCRIPTION
        "Row describing the linker configuration between VOIP and radio channels."
    INDEX   { omniLinkerVoipChannelIndex }
    ::= { omniLinkerVoipTable 1 }

OmniLinkerVoipEntry ::= SEQUENCE {
    omniLinkerVoipChannelIndex  Integer32,
    omniLinkerVoipChannelName   DisplayString,
    omniLinkerRadioChannel1     Integer32,
    omniLinkerRadioChannel2     Integer32,
    omniLinkerRadioChannel3     Integer32,
    omniLinkerRadioChannel4     Integer32,
    omniLinkerAudioBridge       Integer32
}

omniLinkerVoipChannelIndex OBJECT-TYPE
    SYNTAX      Integer32(0..128)
    MAX-ACCESS  not-accessible
    STATUS      current
    DESCRIPTION
        "Index of Linker VOIP table and also the index of the VOIP channel"
    ::= { omniLinkerVoipEntry 1 }

omniLinkerVoipChannelName OBJECT-TYPE
    SYNTAX      DisplayString
    MAX-ACCESS  read-only
    STATUS      current
    DESCRIPTION
        "Name / SDES Location of channel"
    ::= { omniLinkerVoipEntry 2 }

omniLinkerRadioChannel1 OBJECT-TYPE
    SYNTAX      Integer32(0..1)
    MAX-ACCESS  read-write
    STATUS      current
    DESCRIPTION
        "Indicates if radio channel 1 is linked to the VOIP channel (see VOIP channel name for that row),
        where 1 is linked and 0 is not linked."
    ::= { omniLinkerVoipEntry 3 }

omniLinkerRadioChannel2 OBJECT-TYPE
    SYNTAX      Integer32(0..1)
    MAX-ACCESS  read-write
    STATUS      current
    DESCRIPTION
        "Indicates if radio channel 2 is linked to the VOIP channel (see VOIP channel name for that row),
        where 1 is linked and 0 is not linked."
    ::= { omniLinkerVoipEntry 4 }

omniLinkerRadioChannel3 OBJECT-TYPE
    SYNTAX      Integer32(0..1)
    MAX-ACCESS  read-write
    STATUS      current
    DESCRIPTION
        "Indicates if radio channel 3 is linked to the VOIP channel (see VOIP channel name for that row),
        where 1 is linked and 0 is not linked."
    ::= { omniLinkerVoipEntry 5 }

omniLinkerRadioChannel4 OBJECT-TYPE
    SYNTAX      Integer32(0..1)
    MAX-ACCESS  read-write
    STATUS      current
    DESCRIPTION
        "Indicates if radio channel 4 is linked to the VOIP channel (see VOIP channel name for that row),
        where 1 is linked and 0 is not linked."
    ::= { omniLinkerVoipEntry 6 }

omniLinkerAudioBridge OBJECT-TYPE
    SYNTAX      Integer32(0..1)
    MAX-ACCESS  read-write
    STATUS      current
    DESCRIPTION
        "Indicates whether all radio channels linked to the VOIP channel are bridged,
        where 1 is bridged and 0 implies the audio is not bridged."
    ::= { omniLinkerVoipEntry 7 }

omniLinkerAudioBridgeTable OBJECT-TYPE
    SYNTAX      SEQUENCE OF OmniLinkerAudioBridgeEntry
    MAX-ACCESS  not-accessible
    STATUS      current
    DESCRIPTION
        "This table allows audio to be bridged between radios without VOIP."
    ::=  { omniLinker 2 }

omniLinkerAudioBridgeEntry OBJECT-TYPE
    SYNTAX      OmniLinkerAudioBridgeEntry
    MAX-ACCESS  not-accessible
    STATUS      current
    DESCRIPTION
        "Row that describes how each radio's audio is bridged."
    INDEX   { omniLinkerRadioChannelIndex }
    ::= { omniLinkerAudioBridgeTable 1 }

OmniLinkerAudioBridgeEntry ::= SEQUENCE {
    omniLinkerRadioChannelIndex Integer32,
    omniLinkerRadioChannelName  DisplayString,
    omniLinkerLocalGroup1       Integer32,
    omniLinkerLocalGroup2       Integer32
}

omniLinkerRadioChannelIndex OBJECT-TYPE
    SYNTAX      Integer32(0..3)
    MAX-ACCESS  not-accessible
    STATUS      current
    DESCRIPTION
        "This is the index of the Linker Audio Bridge table and also the index of the radio channel."
    ::= { omniLinkerAudioBridgeEntry 1 }

omniLinkerRadioChannelName OBJECT-TYPE
    SYNTAX      DisplayString
    MAX-ACCESS  read-only
    STATUS      current
    DESCRIPTION
        "Name of radio channel"
    ::= { omniLinkerAudioBridgeEntry 2 }

omniLinkerLocalGroup1 OBJECT-TYPE
    SYNTAX      Integer32(0..1)
    MAX-ACCESS  read-write
    STATUS      current
    DESCRIPTION
        "Two groups are provided to allow the user to specify how each radio's audio is bridged.
        All radios selected (by giving a value of 1) in a particular group will have their audio bridged.
        A radio can be removed from a group by entering 0."
    ::= { omniLinkerAudioBridgeEntry 3 }

omniLinkerLocalGroup2 OBJECT-TYPE
    SYNTAX      Integer32(0..1)
    MAX-ACCESS  read-write
    STATUS      current
    DESCRIPTION
        "Two groups are provided to allow the user to specify how each radio's audio is bridged.
        All radios selected (by giving a value of 1) in a particular group will have their audio bridged.
        A radio can be removed from a group by entering 0."
    ::= { omniLinkerAudioBridgeEntry 4 }

---
---  Status information objects for Spectra Digital Radios: spectraStatus
---
spectraLEDAlarm OBJECT-TYPE
    SYNTAX Integer32(0..1)
    MAX-ACCESS read-only
    STATUS current
    DESCRIPTION
         "Alarm LED (0 for off and 1 for on)"
    ::= { omniRadioStatusEntry 5 }

spectraLEDLockDetect OBJECT-TYPE
    SYNTAX Integer32(0..1)
    MAX-ACCESS read-only
    STATUS current
    DESCRIPTION
         "Lock detect LED (0 for off and 1 for on)"
    ::= { omniRadioStatusEntry 6 }

spectraLEDCTCSS OBJECT-TYPE
    SYNTAX Integer32(0..1)
    MAX-ACCESS read-only
    STATUS current
    DESCRIPTION
         "CTCSS or Low supply voltage LED (0 for off and 1 for on)"
    ::= { omniRadioStatusEntry 7 }

spectraLEDPTT OBJECT-TYPE
    SYNTAX Integer32(0..1)
    MAX-ACCESS read-only
    STATUS current
    DESCRIPTION
         "PTT LED (0 for off and 1 for on)"
    ::= { omniRadioStatusEntry 8 }

spectraLEDMute OBJECT-TYPE
    SYNTAX Integer32(0..1)
    MAX-ACCESS read-only
    STATUS current
    DESCRIPTION
         "Mute LED (0 for off and 1 for on)"
    ::= { omniRadioStatusEntry 9 }

spectraLEDPower OBJECT-TYPE
    SYNTAX Integer32(0..1)
    MAX-ACCESS read-only
    STATUS current
    DESCRIPTION
         "Power LED (0 for off and 1 for on)"
    ::= { omniRadioStatusEntry 10 }

spectraAlarmLowForwardPower OBJECT-TYPE
    SYNTAX Integer32(0..1)
    MAX-ACCESS read-only
    STATUS current
    DESCRIPTION
         "Low forward power (0 for off and 1 for on)"
    ::= { omniRadioStatusEntry 11 }

spectraAlarmHighReflectedPower OBJECT-TYPE
    SYNTAX Integer32(0..1)
    MAX-ACCESS read-only
    STATUS current
    DESCRIPTION
         "High reflected power (0 for off and 1 for on)"
    ::= { omniRadioStatusEntry 12 }

spectraAlarmLowInputVoltage OBJECT-TYPE
    SYNTAX Integer32(0..1)
    MAX-ACCESS read-only
    STATUS current
    DESCRIPTION
         "Low power supply input voltage (0 for off and 1 for on)"
    ::= { omniRadioStatusEntry 13 }

spectraAlarmHighInputVoltage OBJECT-TYPE
    SYNTAX Integer32(0..1)
    MAX-ACCESS read-only
    STATUS current
    DESCRIPTION
         "High power supply input voltage (0 for off and 1 for on)"
    ::= { omniRadioStatusEntry 14 }

spectraAlarmTransmitterOutOfLock OBJECT-TYPE
    SYNTAX Integer32(0..1)
    MAX-ACCESS read-only
    STATUS current
    DESCRIPTION
         "Transmitter out of lock (0 for off and 1 for on)"
    ::= { omniRadioStatusEntry 15 }

spectraAlarmReceiverOutOfLock OBJECT-TYPE
    SYNTAX Integer32(0..1)
    MAX-ACCESS read-only
    STATUS current
    DESCRIPTION
         "Receiver out of lock (0 for off and 1 for on)"
    ::= { omniRadioStatusEntry 16 }

spectraAlarmPAOverTemperature OBJECT-TYPE
    SYNTAX Integer32(0..1)
    MAX-ACCESS read-only
    STATUS current
    DESCRIPTION
         "PA over-temperature (0 for off and 1 for on)"
    ::= { omniRadioStatusEntry 17 }

spectraOpenCollectorPolarity OBJECT-TYPE
    SYNTAX Integer32(0..1)
    MAX-ACCESS read-only
    STATUS current
    DESCRIPTION
         "Open collector polarity (0 for low and 1 for high)"
    ::= { omniRadioStatusEntry 18 }

---
---  Product Specific Information
---

---
--- IPE information: ipe
---

ipeMode OBJECT-TYPE
    SYNTAX DisplayString (SIZE (4))
    MAX-ACCESS read-only
    STATUS     current
    DESCRIPTION
    "Operating mode of this IPE. LIU mode for radio channels, OPR mode for operator positions"
    ::= { ipe 1 }

ipeDx64Address OBJECT-TYPE
    SYNTAX Integer32(0..32)
    MAX-ACCESS read-only
    STATUS     current
    DESCRIPTION
    "Address on the Dx64 for this card"
    ::= { ipe 2 }

---
--- AFI IP information: afi
---

afiOperatorPosition OBJECT-TYPE
    SYNTAX Integer32(0..32)
    MAX-ACCESS read-only
    STATUS     current
    DESCRIPTION
    "The operator position associated with the AFI"
    ::= { afi 1 }

afiOperatorPushToTalk OBJECT-TYPE
    SYNTAX      Integer32(0..1)
    MAX-ACCESS read-only
    STATUS     current
    DESCRIPTION
    "State of the AFI operator Push To Talk status
        True when the operator is pressing push to talk on
        any device or switch connected to the AFI"
    ::= { afi 2 }

afiOperatorBusy OBJECT-TYPE
    SYNTAX      Integer32(0..1)
    MAX-ACCESS read-only
    STATUS     current
    DESCRIPTION
    "State of the AFI operator busy status
        True when the operator is RX audio from
        one or more radio channels in the foreground or background
        workgroups"
    ::= { afi 3 }

afiOperatorTalkCounts OBJECT-TYPE
    SYNTAX Counter32
    MAX-ACCESS read-only
    STATUS current
    DESCRIPTION
        "The number of times the operator has talked, pressed the push to talk button in the last 15 minutes"
     ::= { afi 4 }

afiOperatorListenCounts OBJECT-TYPE
    SYNTAX Counter32
    MAX-ACCESS read-only
    STATUS current
    DESCRIPTION
        "The number of times the operator listened to a radio call in the last 15 minutes"
     ::= { afi 5 }

afiOperatorConversationCounts OBJECT-TYPE
    SYNTAX Counter32
    MAX-ACCESS read-only
    STATUS current
    DESCRIPTION
        "The number of times the operator talked or listened to a radio in the last 15 minutes"
     ::= { afi 6 }

afiOperatorTalkSeconds OBJECT-TYPE
    SYNTAX Counter32
    MAX-ACCESS read-only
    STATUS current
    DESCRIPTION
        "The amount of time, in seconds, this operator position has been talking
         to radios in the last 15 minutes"
     ::= { afi 7 }

afiOperatorListenSeconds OBJECT-TYPE
    SYNTAX Counter32
    MAX-ACCESS read-only
    STATUS current
    DESCRIPTION
        "The amount of time, in seconds, this operator position has been listening
         to radios in the last 15 minutes"
     ::= { afi 8 }

afiOperatorConversationSeconds OBJECT-TYPE
    SYNTAX Counter32
    MAX-ACCESS read-only
    STATUS current
    DESCRIPTION
        "The amount of time, in seconds, this operator position has been listening or
        talking in the last 15 minutes"
     ::= { afi 9 }


---
---  IPR400 Information
---

---
---  IPR400 Traps
---
ipr400Trap         OBJECT IDENTIFIER ::=  { ipr400 0 }

---
---  Notification Objects: ipr400Trap
---
ipr400DigitalInput1Trap  NOTIFICATION-TYPE
     OBJECTS {
        ipr400DigitalInput1
     }
     STATUS current
     DESCRIPTION
         "Digital input 1 changed state"
     ::= { ipr400Trap 1 }

ipr400DigitalInput2Trap  NOTIFICATION-TYPE
     OBJECTS {
        ipr400DigitalInput2
     }
     STATUS current
     DESCRIPTION
         "Digital input 2 changed state"
     ::= { ipr400Trap 2 }

ipr400AnalogInput1Trap  NOTIFICATION-TYPE
     OBJECTS {
        ipr400AnalogInput1
     }
     STATUS current
     DESCRIPTION
         "Analog input 1 crossed high or low threshold"
     ::= { ipr400Trap 3 }

ipr400AnalogInput2Trap  NOTIFICATION-TYPE
     OBJECTS {
        ipr400AnalogInput2
     }
     STATUS current
     DESCRIPTION
         "Analog input 2 crossed high or low threshold"
     ::= { ipr400Trap 4 }

ipr400AnalogInput3Trap  NOTIFICATION-TYPE
     OBJECTS {
        ipr400AnalogInput3
     }
     STATUS current
     DESCRIPTION
         "Analog Input 3 crossed high or low threshold"
     ::= { ipr400Trap 5 }

ipr400AnalogInput4Trap  NOTIFICATION-TYPE
     OBJECTS {
        ipr400AnalogInput4
     }
     STATUS current
     DESCRIPTION
         "Analog Input 4 crossed high or low threshold"
     ::= { ipr400Trap 6 }

ipr400AnalogInput5Trap  NOTIFICATION-TYPE
     OBJECTS {
        ipr400AnalogInput5
     }
     STATUS current
     DESCRIPTION
         "Analog Input 5 crossed high or low threshold"
     ::= { ipr400Trap 7 }

ipr400AnalogInput6Trap  NOTIFICATION-TYPE
     OBJECTS {
        ipr400AnalogInput6
     }
     STATUS current
     DESCRIPTION
         "Analog Input 6 crossed high or low threshold"
            ::= { ipr400Trap 8 }

ipr400AnalogInput7Trap  NOTIFICATION-TYPE
     OBJECTS {
        ipr400AnalogInput7
     }
     STATUS current
     DESCRIPTION
         "Analog Input 7 crossed high or low threshold"
     ::= { ipr400Trap 9 }

ipr400AnalogInput8Trap  NOTIFICATION-TYPE
     OBJECTS {
        ipr400AnalogInput8
     }
     STATUS current
     DESCRIPTION
         "Analog Input 8 crossed high or low threshold"
     ::= { ipr400Trap 10 }

ipr400TemperatureTrap  NOTIFICATION-TYPE
     OBJECTS {
        ipr400Temperature
     }
     STATUS current
     DESCRIPTION
         "Analog Input Temperature crossed high or low threshold"
     ::= { ipr400Trap 11 }

ipr400VoltageTrap  NOTIFICATION-TYPE
     OBJECTS {
        ipr400Voltage
     }
     STATUS current
     DESCRIPTION
         "Analog Input Supply Voltage crossed high or low threshold"
     ::= { ipr400Trap 12 }

---
---  IPR400 Information: ipr400
---

ipr400Version OBJECT-TYPE
    SYNTAX DisplayString (SIZE (255))
    MAX-ACCESS read-only
    STATUS     deprecated
    DESCRIPTION
            "version number for main application (obsolete use the omniVersion OID instead)"
    ::= { ipr400 1 }

ipr400DSPVersion OBJECT-TYPE
    SYNTAX DisplayString (SIZE (255))
    MAX-ACCESS read-only
    STATUS deprecated
    DESCRIPTION
            "Version Number for DSP application (obsolete use the omniVersion OID instead)"
    ::= { ipr400 2 }

ipr400DigitalInput OBJECT IDENTIFIER ::= { ipr400 3 }

ipr400DigitalInput1 OBJECT-TYPE
    SYNTAX Integer32(0..1)
    MAX-ACCESS read-only
    STATUS current
    DESCRIPTION "Current state of digital input 1. Zero is off, one is on"
    ::= { ipr400DigitalInput 1 }

ipr400DigitalInput2 OBJECT-TYPE
    SYNTAX Integer32(0..1)
    MAX-ACCESS read-only
    STATUS current
    DESCRIPTION "Current state of digital input 2"
    ::= { ipr400DigitalInput 2 }

ipr400DigitalOutput OBJECT IDENTIFIER ::= { ipr400 4 }

ipr400DigitalOutput1 OBJECT-TYPE
    SYNTAX Integer32(0..1)
    MAX-ACCESS read-write
    STATUS current
    DESCRIPTION "Digital output 1. Zero is off, one is on"
    ::= { ipr400DigitalOutput 1 }

ipr400DigitalOutput2 OBJECT-TYPE
    SYNTAX Integer32(0..1)
    MAX-ACCESS read-write
    STATUS current
    DESCRIPTION "Digital output 2. Zero is off, one is on"
    ::= { ipr400DigitalOutput 2 }

ipr400AnalogInputs OBJECT IDENTIFIER ::= { ipr400 5 }

ipr400AnalogInput1 OBJECT-TYPE
    SYNTAX Integer32(0..5000)
    MAX-ACCESS read-only
    STATUS current
    DESCRIPTION "Analog input 1, value in millivolts"
    ::= { ipr400AnalogInputs 1 }

ipr400AnalogInput2 OBJECT-TYPE
    SYNTAX Integer32(0..5000)
    MAX-ACCESS read-only
    STATUS current
    DESCRIPTION "Analog input 2, value in millivolts"
    ::= { ipr400AnalogInputs 2 }

ipr400AnalogInput3 OBJECT-TYPE
    SYNTAX Integer32(0..5000)
    MAX-ACCESS read-only
    STATUS current
    DESCRIPTION "Analog input 3, value in millivolts"
    ::= { ipr400AnalogInputs 3 }

ipr400AnalogInput4 OBJECT-TYPE
    SYNTAX Integer32(0..5000)
    MAX-ACCESS read-only
    STATUS current
    DESCRIPTION "Analog input 4, value in millivolts"
    ::= { ipr400AnalogInputs 4 }

ipr400AnalogInput5 OBJECT-TYPE
    SYNTAX Integer32(0..5000)
    MAX-ACCESS read-only
    STATUS current
    DESCRIPTION "Analog input 5, value in millivolts"
    ::= { ipr400AnalogInputs 5 }

ipr400AnalogInput6 OBJECT-TYPE
    SYNTAX Integer32(0..5000)
    MAX-ACCESS read-only
    STATUS current
    DESCRIPTION "Analog input 6, value in millivolts"
    ::= { ipr400AnalogInputs 6 }

ipr400AnalogInput7 OBJECT-TYPE
    SYNTAX Integer32(0..5000)
    MAX-ACCESS read-only
    STATUS current
    DESCRIPTION "Analog input 7, value in millivolts"
    ::= { ipr400AnalogInputs 7 }

ipr400AnalogInput8 OBJECT-TYPE
    SYNTAX Integer32(0..5000)
    MAX-ACCESS read-only
    STATUS current
    DESCRIPTION "Analog input 8, value in millivolts"
    ::= { ipr400AnalogInputs 8 }

ipr400Temperature OBJECT-TYPE
    SYNTAX Integer32(0..128)
    MAX-ACCESS read-only
    STATUS current
    DESCRIPTION "Site Temperature, in degrees C"
    ::= { ipr400AnalogInputs 9 }

ipr400Voltage OBJECT-TYPE
    SYNTAX Integer32(0..40000)
    MAX-ACCESS read-only
    STATUS current
    DESCRIPTION "Site Voltage (value in millivolts) "
    ::= { ipr400AnalogInputs 10 }

---
--- DX64 information
---

dx64Trap         OBJECT IDENTIFIER ::=  { dx64 0 }

informationTrap  NOTIFICATION-TYPE
     OBJECTS {
        messageInformation
     }
     STATUS current
     DESCRIPTION
         "DX64 General Information Message"
     ::= { dx64Trap 1 }

warningTrap  NOTIFICATION-TYPE
     OBJECTS {
        messageWarning
     }
     STATUS current
     DESCRIPTION
         "DX64 General Warning Message"
     ::= { dx64Trap 2 }

errorTrap  NOTIFICATION-TYPE
     OBJECTS {
        messageError
     }
     STATUS current
     DESCRIPTION
         "DX64 General Error Message"
     ::= { dx64Trap 3 }

messages         OBJECT IDENTIFIER ::=  { dx64 1 }

messageInformation OBJECT-TYPE
    SYNTAX DisplayString (SIZE (255))
    MAX-ACCESS read-only
    STATUS current
    DESCRIPTION
        "DX64 General Information Message"
    ::= { messages 1 }

messageWarning OBJECT-TYPE
    SYNTAX DisplayString (SIZE (255))
    MAX-ACCESS read-only
    STATUS current
    DESCRIPTION
        "DX64 General Warning Message"
    ::= { messages 2 }

messageError OBJECT-TYPE
    SYNTAX DisplayString (SIZE (255))
    MAX-ACCESS read-only
    STATUS current
    DESCRIPTION
        "DX64 General Error Message"
    ::= { messages 3 }



--
-- Compliance. These are to ensure the format is valid, can not be read from the device
--
omniVersionGroup OBJECT-GROUP
    OBJECTS{
        applicationVersion,
        dspVersion,
        serialNumber,
        hardwareRevision
    }
    STATUS current
    DESCRIPTION "Objects related to version information and serial numbers"
        ::= { omniMIBGroups 1 }

omniRadioGroup OBJECT-GROUP
    OBJECTS{
       omniRadioNumberOfChannels,
       omniRadioChannelName,
       omniRadioPushToTalk,
       omniRadioBusy,
       spectraLEDAlarm,
       spectraLEDLockDetect,
       spectraLEDCTCSS,
       spectraLEDPTT,
       spectraLEDMute,
       spectraLEDPower,
       spectraAlarmLowForwardPower,
       spectraAlarmHighReflectedPower,
       spectraAlarmLowInputVoltage,
       spectraAlarmHighInputVoltage,
       spectraAlarmTransmitterOutOfLock,
       spectraAlarmReceiverOutOfLock,
       spectraAlarmPAOverTemperature,
       spectraOpenCollectorPolarity
    }
    STATUS current
    DESCRIPTION "Objects related to the a radio channel"
        ::= { omniMIBGroups 2 }

omniVoipGroup OBJECT-GROUP
    OBJECTS {
       omniVoipNumberOfChannels,
       omniVoipChannelName,
       omniVoipLinkUp,
       omniVoipABCDState,
       omniVoipTransmitPackets,
       omniVoipRxPackets,
       omniVoipRxTooLatePackets,
       omniVoipRxSequenceErrorPackets,
       omniRadioChannelNumber
    }
    STATUS current
    DESCRIPTION "Objects related to the a voip channel"
        ::= { omniMIBGroups 3 }

omniNotificationGroup NOTIFICATION-GROUP
        NOTIFICATIONS {
           omniEventPushToTalkTimeout,
           omniEventVoipLinkStatus,
           omniEventVoipRxTooLatePackets,
           omniEventVoipRxSeqErrPackets,
           omniEventConfigChange,
           omniEventInformation,
           omniEventWarning,
           omniEventError,
           ipr400AnalogInput1Trap,ipr400AnalogInput2Trap,ipr400AnalogInput3Trap,ipr400AnalogInput4Trap,
           ipr400AnalogInput5Trap,ipr400AnalogInput6Trap,ipr400AnalogInput7Trap,ipr400AnalogInput8Trap,
           ipr400VoltageTrap, ipr400TemperatureTrap,
           ipr400DigitalInput1Trap, ipr400DigitalInput2Trap,
           informationTrap, warningTrap, errorTrap,
		   omnicoreConsoleServerConnectionTrap
        }
        STATUS current
        DESCRIPTION
                "Notifications."
        ::= { omniMIBGroups 4 }

omniDeprecatedGroup OBJECT-GROUP
    OBJECTS {
       ipr400DSPVersion, ipr400Version
    }
    STATUS deprecated
    DESCRIPTION "Deprecated objects."
        ::=  { omniMIBGroups 5 }


ipr400ProductSpecificGroup OBJECT-GROUP
    OBJECTS {
       ipr400AnalogInput1,ipr400AnalogInput2,ipr400AnalogInput3,ipr400AnalogInput4,
       ipr400AnalogInput5,ipr400AnalogInput6,ipr400AnalogInput7,ipr400AnalogInput8,
       ipr400Voltage, ipr400Temperature,
       ipr400DigitalOutput1, ipr400DigitalOutput2,
       ipr400DigitalInput1, ipr400DigitalInput2
    }
    STATUS current
    DESCRIPTION "Objects related to the IPR400 Product"
        ::= { omniMIBGroups 6 }

afiProductSpecificGroup OBJECT-GROUP
    OBJECTS {
       afiOperatorPosition, afiOperatorBusy, afiOperatorPushToTalk,
       afiOperatorTalkCounts, afiOperatorListenCounts, afiOperatorConversationCounts,
       afiOperatorTalkSeconds, afiOperatorListenSeconds, afiOperatorConversationSeconds
    }
    STATUS current
    DESCRIPTION "Objects related to the Dx64 AFI-IP product"
        ::= { omniMIBGroups 7 }

ipeProductSpecificGroup OBJECT-GROUP
    OBJECTS {
       ipeMode, ipeDx64Address
    }
    STATUS current
    DESCRIPTION "Objects related to the Dx64 IPE product"
        ::= { omniMIBGroups 8 }

dx64ProductSpecificGroup OBJECT-GROUP
    OBJECTS {
       messageInformation, messageWarning, messageError
    }
    STATUS current
    DESCRIPTION "Objects related to the Dx64 product"
        ::= { omniMIBGroups 9 }

omniMessageGroup OBJECT-GROUP
    OBJECTS {
        omniInformationMessage, omniWarningMessage, omniErrorMessage
    }
    STATUS current
    DESCRIPTION
        "Messages related to Omnitronics products."
        ::= { omniMIBGroups 10 }

omniLinkerGroup OBJECT-GROUP
    OBJECTS{
       omniLinkerRadioChannelName,
       omniLinkerLocalGroup1,
       omniLinkerLocalGroup2,
       omniLinkerVoipChannelName,
       omniLinkerRadioChannel1,
       omniLinkerRadioChannel2,
       omniLinkerRadioChannel3,
       omniLinkerRadioChannel4,
       omniLinkerAudioBridge
    }
    STATUS current
    DESCRIPTION "Objects related to the linker"
        ::= { omniMIBGroups 11 }

omniRadioNotificationGroup NOTIFICATION-GROUP
    NOTIFICATIONS {
        spectraEvtAlarm,
        spectraEvtLockDetect,
        spectraEvtCTCSS,
        spectraEvtPTT,
        spectraEvtMute,
        spectraEvtPower,
        spectraEvtLowForwardPower,
        spectraEvtHighReflectedPower,
        spectraEvtLowInputVoltage,
        spectraEvtHighInputVoltage,
        spectraEvtTransmitterOutOfLock,
        spectraEvtReceiverOutOfLock,
        spectraEvtPAOverTemperature,
        spectraEvtOpenCollectorPolarity
    }
    STATUS current
    DESCRIPTION
        "These objects describe events available for digital radios."
        ::= { omniMIBGroups 12 }

omniDigitalRadioMessageGroup OBJECT-GROUP
OBJECTS {
        spectraLEDAlarm,
        spectraLEDLockDetect,
        spectraLEDCTCSS,
        spectraLEDPTT,
        spectraLEDMute,
        spectraLEDPower,
        spectraAlarmLowForwardPower,
        spectraAlarmHighReflectedPower,
        spectraAlarmLowInputVoltage,
        spectraAlarmHighInputVoltage,
        spectraAlarmTransmitterOutOfLock,
        spectraAlarmReceiverOutOfLock,
        spectraAlarmPAOverTemperature,
        spectraOpenCollectorPolarity
    }
    STATUS current
    DESCRIPTION
        "These objects describe messages available for digital radios."
        ::= { omniMIBGroups 13 }

  
--
-- TetraGateway 
--

tetragatewayRadioStatus OBJECT-TYPE
    SYNTAX      Integer32(0..1)
    MAX-ACCESS  read-only
    STATUS      current
    DESCRIPTION
    "Current status of the Damm TetraFlex Radio System: 0=Offline, 1=ONLINE"
    ::= { tetragateway 1 }

tetragatewayGatewayStatus OBJECT-TYPE
    SYNTAX      DisplayString 
    MAX-ACCESS  read-only
    STATUS      current
    DESCRIPTION
    "Status of the Damm TetraFlex Radio System"
    ::= { tetragateway 2 }


tetragatewayRadioDescription  OBJECT-TYPE
    SYNTAX      DisplayString 
    MAX-ACCESS  read-only
    STATUS      current
    DESCRIPTION
    "Description from the Damm Radio Base (provided by the DAMM API)"
    ::= { tetragateway 3 }


tetragatewayUserIdentity  OBJECT-TYPE
    SYNTAX      DisplayString 
    MAX-ACCESS  read-only
    STATUS      current
    DESCRIPTION
    "Tetra User ID Associated with this Tetragateway"
    ::= { tetragateway 4 }

tetragatewayLicenseStatus OBJECT-TYPE
    SYNTAX      DisplayString 
    MAX-ACCESS  read-only
    STATUS      current
    DESCRIPTION
    "Status of the Omnitronics License of the Tetragateway "
    ::= { tetragateway 5 }

tetragatewayConsoleCount OBJECT-TYPE
    SYNTAX      Integer32(0..128)
    MAX-ACCESS  read-only
    STATUS      current
    DESCRIPTION
    "Number of consoles currently connected to the gateway"
    ::= { tetragateway 6 }

tetragatewayFailOverState OBJECT-TYPE
    SYNTAX      Integer32(0..4)
    MAX-ACCESS  read-only
    STATUS      current
    DESCRIPTION
    "If using automatic fail-over, this is the current state of the TetraGateway-DM fail-over. 
	Possible value are 
		0:Not Used or Starting up 
		1:Active 
		2:Active_Manual_Only 
		3:Standby 
		4:Standby_Manual_Only
		
	In the manual only states, a manual fail-over is required to rearm automatic fail-over"
    ::= { tetragateway 7 }

tetragatewayFailOverStateString OBJECT-TYPE
    SYNTAX      DisplayString 
    MAX-ACCESS  read-only
    STATUS      current
    DESCRIPTION
    "If using automatic fail-over, this a text description of the current state of the TetraGateway-DM fail-over. 
	Possible values are 'Starting', 'Active', 'Active_Manual_Only','Standby' or 'Standby_Manual_Only' 
	This value is blank if fail-over function is not enabled"
    ::= { tetragateway 8 }
	

tetragatewayProductSpecificGroup OBJECT-GROUP
    OBJECTS {
        tetragatewayRadioStatus,
        tetragatewayGatewayStatus,
        tetragatewayRadioDescription,
		tetragatewayUserIdentity,
        tetragatewayLicenseStatus,
        tetragatewayConsoleCount,
		tetragatewayFailOverState,
		tetragatewayFailOverStateString
    }
    STATUS current
    DESCRIPTION "Objects related to the TetraGateway"
        ::= { omniMIBGroups 14 }
		
		
--
-- omnicoreWeb
--
	
omnicoreWebConsoleCount OBJECT-TYPE
    SYNTAX      Integer32(0..128)
    MAX-ACCESS  read-only
    STATUS      current
    DESCRIPTION
    "Number of consoles currently connected"
    ::= { omnicoreWeb 1 }


omnicoreWebProductSpecificGroup OBJECT-GROUP
    OBJECTS {
        omnicoreWebConsoleCount

    }
    STATUS current
    DESCRIPTION "Objects related to the omnicoreWeb"
        ::= { omniMIBGroups 15 }
		
		
--
-- omnicoreConsole
--


--
--  omnicore Console Traps
--
omnicoreConsoleTrap         OBJECT IDENTIFIER ::=  { omnicoreConsole 0 }

---
---  Notification Objects: omnicoreConsoleTrap
---
omnicoreConsoleServerConnectionTrap  NOTIFICATION-TYPE
     OBJECTS {
        omnicoreConsoleServerStatus
     }
     STATUS current
     DESCRIPTION
         "omnicore Console Connection Trap: 0=Disconnected, 1=Connected "
     ::= { omnicoreConsoleTrap 1 }
	
	
omnicoreConsoleServerStatus OBJECT-TYPE
    SYNTAX      Integer32(0..128)
    MAX-ACCESS  read-only
    STATUS      current
    DESCRIPTION
    "Current status of the Server Connection: 0=Disconnected, 1=Connected"
    ::= { omnicoreConsole 1 }

omnicoreConsoleServerVersion OBJECT-TYPE
    SYNTAX DisplayString (SIZE (255))
    MAX-ACCESS read-only
    STATUS current
    DESCRIPTION
        "Version number of Connected omnicore Server"
    ::= { omnicoreConsole 2 }

omnicoreConsoleProductSpecificGroup OBJECT-GROUP
    OBJECTS {
        omnicoreConsoleServerStatus,
		omnicoreConsoleServerVersion
    }
    STATUS current
    DESCRIPTION "Objects related to the omnicoreConsole"
        ::= { omniMIBGroups 16 }

---
---  Omnigate
---

omnigateVersion OBJECT-TYPE
    SYNTAX DisplayString
    MAX-ACCESS read-only
    STATUS     current
    DESCRIPTION
    "Version number of Omnigate"
    ::= { omnigate 1 }

omnigateBuildDate OBJECT-TYPE
    SYNTAX DisplayString
    MAX-ACCESS  read-only
    STATUS      current
    DESCRIPTION
    "Build Date"
    ::= { omnigate 2 }
    
omnigateConfigurationStatus OBJECT-TYPE
    SYNTAX DisplayString
    MAX-ACCESS  read-only
    STATUS      current
    DESCRIPTION
    "Current status of the Omnigate Configuration: 0=Disconnected, 1=Connected"
    ::= { omnigate 3 }
            
---
---  Voip Information: omnigate
---
omnigateNumberOfChannels OBJECT-TYPE
    SYNTAX Integer32(0..128)
    MAX-ACCESS read-only
    STATUS current
    DESCRIPTION "Number of Voip Channels supported by this device"
        ::= { omnigate 4 }

omnigateGatewaysTable OBJECT-TYPE
    SYNTAX      SEQUENCE OF OmnigateStatusEntry
    MAX-ACCESS  not-accessible
    STATUS      current
    DESCRIPTION
        "Table contains the status of VoIP links"
    ::=  { omnigate 5 }

omnigateStatusEntry OBJECT-TYPE
        SYNTAX      OmnigateStatusEntry
        MAX-ACCESS  not-accessible
        STATUS      current
        DESCRIPTION
            "Row describes status of a Logical Gateway"
        INDEX   { omnigateChannelIndex }
        ::= { omnigateGatewaysTable 1 }

OmnigateStatusEntry ::=
    SEQUENCE {
        omnigateChannelIndex           Integer32,
        omnigateGatewayName            DisplayString,
        omnigateCCPStatus              Integer32,
        omnigateVoIPStatus             Integer32,
        omnigateRadioStatus            Integer32
    }

omnigateChannelIndex OBJECT-TYPE
    SYNTAX      Integer32(0..128)
    MAX-ACCESS  not-accessible
    STATUS      current
    DESCRIPTION
        "Index for omnigate table"
    ::= { omnigateStatusEntry 1 }

omnigateGatewayName OBJECT-TYPE
    SYNTAX      DisplayString
    MAX-ACCESS  read-only
    STATUS      current
    DESCRIPTION
    "Gateway Name "
    ::= { omnigateStatusEntry 2 }

omnigateCCPStatus OBJECT-TYPE
    SYNTAX      Integer32(0..1)
    MAX-ACCESS  read-only
    STATUS      current
    DESCRIPTION
    "Status of the CCP link. 0=Offline, 1=online, 255=Disabled "
    ::= { omnigateStatusEntry 3 }

omnigateVoIPStatus OBJECT-TYPE
    SYNTAX      Integer32(0..1)
    MAX-ACCESS  read-only
    STATUS      current
    DESCRIPTION
    "VoIP status. 0=Offline, 1=online, 255=Disabled "
    ::= { omnigateStatusEntry 4 }

omnigateRadioStatus OBJECT-TYPE
    SYNTAX      Integer32
    MAX-ACCESS  read-only
    STATUS      current
    DESCRIPTION
    "Radio Status. 0=Offline, 1=online, 255=Disabled "
    ::= { omnigateStatusEntry 5 }

omnigateProductSpecificGroup OBJECT-GROUP
    OBJECTS {
       omnigateVersion,
	   omnigateBuildDate,
	   omnigateConfigurationStatus, 
	   omnigateRadioStatus,
	   omnigateNumberOfChannels,
	   omnigateVoIPStatus,
	   omnigateCCPStatus,
	   omnigateGatewayName
    }
    STATUS current
    DESCRIPTION "Objects related to the omnigate"
        ::= { omniMIBGroups 17 }

---
--- omnihub
---

omnihubOperatorPushToTalk OBJECT-TYPE
    SYNTAX      Integer32(0..1)
    MAX-ACCESS read-only
    STATUS     current
    DESCRIPTION
    "State of the omnihub operator Push To Talk status
        1 when the operator is pressing push to talk on
        any device or switch connected to the omnihub"
    ::= { omnihub 1 }

omnihubOperatorBusy OBJECT-TYPE
    SYNTAX      Integer32(0..1)
    MAX-ACCESS read-only
    STATUS     current
    DESCRIPTION
    "State of the omnihub operator busy status
        1 when the operator is receiving audio from
        one or more radio channels in the foreground or background
        workgroups"
    ::= { omnihub 2 }

omnihubOperatorTalkCounts OBJECT-TYPE
    SYNTAX Counter32
    MAX-ACCESS read-only
    STATUS current
    DESCRIPTION
        "The number of times the operator has talked, pressed the push to talk button in the last 15 minutes"
     ::= { omnihub 3 }

omnihubOperatorListenCounts OBJECT-TYPE
    SYNTAX Counter32
    MAX-ACCESS read-only
    STATUS current
    DESCRIPTION
        "The number of times the operator listened to incoming radio audio in the last 15 minutes"
     ::= { omnihub 4 }

omnihubOperatorConversationCounts OBJECT-TYPE
    SYNTAX Counter32
    MAX-ACCESS read-only
    STATUS current
    DESCRIPTION
        "The number of times the operator talked or listened to a radio in the last 15 minutes"
     ::= { omnihub 5 }

omnihubOperatorTalkSeconds OBJECT-TYPE
    SYNTAX Counter32
    MAX-ACCESS read-only
    STATUS current
    DESCRIPTION
        "The amount of time, in seconds, the operator has been talking
         to radios in the last 15 minutes"
     ::= { omnihub 6 }

omnihubOperatorListenSeconds OBJECT-TYPE
    SYNTAX Counter32
    MAX-ACCESS read-only
    STATUS current
    DESCRIPTION
        "The amount of time, in seconds, the operator has been listening
         to radios in the last 15 minutes"
     ::= { omnihub 7 }

omnihubOperatorConversationSeconds OBJECT-TYPE
    SYNTAX Counter32
    MAX-ACCESS read-only
    STATUS current
    DESCRIPTION
        "The amount of time, in seconds, the operator has been listening or
        talking in the last 15 minutes"
     ::= { omnihub 8 }

omnihubOperatorPabxPhoneActive OBJECT-TYPE
    SYNTAX      Integer32(0..1)
    MAX-ACCESS read-only
    STATUS     current
    DESCRIPTION
    "Hook State of the omnihub operator PABX Phone
        1 when the PABX Phone is OFF-Hook"
    ::= { omnihub 9 }
	
omnihubOperatorPabxPhoneCounts OBJECT-TYPE
    SYNTAX Counter32
    MAX-ACCESS read-only
    STATUS current
    DESCRIPTION
        "The number of times the operator dealt with a PABX Phone call in the last 15 minutes"
     ::= { omnihub 10 }	
	 
omnihubOperatorPabxPhoneSeconds OBJECT-TYPE
    SYNTAX Counter32
    MAX-ACCESS read-only
    STATUS current
    DESCRIPTION
        "The amount of time, in seconds, the operator spent on the PABX Phone in 
		the last 15 minutes"
     ::= { omnihub 11 }		 

omnihubOperatorConsolePhoneActive OBJECT-TYPE
    SYNTAX      Integer32(0..1)
    MAX-ACCESS read-only
    STATUS     current
    DESCRIPTION
    "Active State of any omnihub operator Console Phone owned
        1 when the operator is owning any Console Phone"
    ::= { omnihub 12 }
	
omnihubOperatorConsolePhoneCounts OBJECT-TYPE
    SYNTAX Counter32
    MAX-ACCESS read-only
    STATUS current
    DESCRIPTION
        "The number of times the operator dealt with a Console Phone call in the last 15 minutes"
     ::= { omnihub 13 }	
	 
omnihubOperatorConsolePhoneSeconds OBJECT-TYPE
    SYNTAX Counter32
    MAX-ACCESS read-only
    STATUS current
    DESCRIPTION
        "The amount of time, in seconds, the operator spent on a Console Phone in 
		the last 15 minutes"
     ::= { omnihub 14 }		 
omnihubProductSpecificGroup OBJECT-GROUP
    OBJECTS {
       omnihubOperatorPushToTalk,
       omnihubOperatorBusy,
       omnihubOperatorTalkCounts,
       omnihubOperatorListenCounts,
       omnihubOperatorConversationCounts,
       omnihubOperatorTalkSeconds,
       omnihubOperatorListenSeconds,
       omnihubOperatorConversationSeconds,
       omnihubOperatorPabxPhoneActive,
       omnihubOperatorPabxPhoneCounts,
       omnihubOperatorPabxPhoneSeconds,
       omnihubOperatorConsolePhoneActive,
       omnihubOperatorConsolePhoneCounts,
       omnihubOperatorConsolePhoneSeconds
    }
    STATUS current
    DESCRIPTION "Objects related to the omnihub product"
        ::= { omniMIBGroups 18 }

END
